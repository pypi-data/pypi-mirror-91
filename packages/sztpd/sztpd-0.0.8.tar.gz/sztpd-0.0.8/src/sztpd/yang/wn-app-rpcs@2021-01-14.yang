module wn-app-rpcs {
  yang-version 1.1;
  namespace "https://watsen.net/app-rpcs";
  prefix app-rpcs;

  import wn-app {
    prefix app;
  }

  organization
    "Watsen Networks (https://watsen.net)";
  description
    "This module defines an RPC used to either to deliver notifications
     (i.e., deined by YANG 'notification' statements) to the HTTP server
     implementing the 'RPC'.  Note that the server need only implement
     support for the 'POST' request (it does not have to implement all
     of the RESTCONF protocol, as might be implied here).

     Copyright (c) 2021 Watsen Networks.  All Rights Reserved.";

  revision 2021-01-14 {
    description
      "Initial version";
  }

  feature relay-notification {
    description
      "Indicates that the 'relay-notification' RPC is supported.";
  }

  identity relay-notification {
    base app:dynamic-callout-rpc;
    description
      "Identifies the 'wn-app-rpcs:relay-notification' RPC.";
  }

  rpc relay-notification {
    if-feature "relay-notification";
    description
      "An RPC for relaying a single 'notification',
       i.e., as defined by a 'notification' statement
       in a YANG module.

       In the case of an error, the RPC MUST return
       the 'ietf-restconf:errors' structure defined
       in Section 7.1 in RFC 8040.";
    input {
      anydata notification;
    }
  }
}
